module shortest-path-config {

    yang-version 1;
    namespace "urn:opendaylight:l2switch:shortest-path-config";
    prefix "shortest-path-config";

    description
        "This module contains the base configuration for shortestpath
        implementation.";

    revision 2014-05-28 {
        description "Initial revision.";
    }

    container shortest-path-config {
        leaf flow-table-id {
            type uint8;
            default 0;
        }
        leaf flow-priority {
            type uint16;
            default 10;
        }
        leaf flow-hard-timeout {
            type uint16;
            default 300;
        }
        leaf flow-idle-timeout {
            type uint16;
            default 600;
        }
        leaf topology-id {
            type string;
            default "flow:1";
        }
    }
}
